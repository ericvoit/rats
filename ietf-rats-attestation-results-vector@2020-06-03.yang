module ietf-rats-attestation-results-vector {
  yang-version 1.1;
  namespace 
     "urn:ietf:params:xml:ns:yang:ietf-rats-attestation-results-vector";
  prefix arv;
  
  import ietf-yang-types {
    prefix yang;
  }
   
  organization "IETF";
  contact
    "WG Web:   <http://tools.ietf.org/wg/rats/>
     WG List:  <mailto:rats@ietf.org>

     Editor:   Eric Voit
               <mailto:evoit@cisco.com>";
               
  description
    "This module contains conceptual YANG specifications for  
    subscribing to attestation streams being generated from TPM chips.
    
    Copyright (c) 2020 IETF Trust and the persons identified as authors 
    of the code.  All rights reserved.

    Redistribution and use in source and binary forms, with or without 
    modification, is permitted pursuant to, and subject to the license 
    terms contained in, the Simplified BSD License set forth in Section 
    4.c of the IETF Trust's Legal Provisions Relating to IETF Documents
    (https://trustee.ietf.org/license-info).

    This version of this YANG module is part of RFC XXXX; see the RFC 
    itself for full legal notices.";
  
  revision 2020-06-03 {
    description
      "Initial version.";    
    reference 
      "draft-voit-rats-trusted-path-routing";
  }


  /*
   * IDENTITIES
   */ 

  identity trustworthiness-level {
    description
      "Base identity for a verifier assessed trustworthiness level.";
  }

  identity trustworthiness-pass {
    description
      "Identity for a verifier assessed trustworthiness pass.";
  }
  
  identity trustworthiness-fail {
    description
      "Base identity for a verifier assessed trustworthiness fail.";
  }

  identity boot-verified {
    base trustworthiness-pass;
    description
      "A Verifier has assessed an Attester as Boot Integrity Verified.";
  }
  
  identity boot-verification-fail {
    base trustworthiness-fail;
    description
      "A Verifier has assessed an Attester has failed its Boot Integrity 
      verification.";
  }

  identity hw-authentic {
    base trustworthiness-pass;
    description
      "A Verifier has assessed an Attester as having authentic hardware.";
  }
  
  identity fw-authentic {
    base trustworthiness-pass;
    description
      "A Verifier has assessed an Attester as having authentic firmware.";
  }
  
  identity hw-verification-fail {
    base trustworthiness-fail;
    description
      "A Verifier has assessed an Attester has failed its hardware or  
      firmware verification.";
  }
  identity identity-verified {
    base trustworthiness-pass;
    description
      "A Verifier has assessed and verified an Attester's unique identity.";
  }
  
  identity identity-fail {
    base trustworthiness-fail;
    description
      "A Verifier has been unable to assess or verify an Attester's unique 
      identity";
  }
  
  identity files-verified {
    base trustworthiness-pass;
    description
      "A Verifier has assessed an Attester's file system, and asserts that
      it recognizes relevant files.";
  }
  
  identity file-blacklisted {
    base trustworthiness-fail;
    description
      "A Verifier has found a file on an Attester which should not be 
      present.";
  }
  
  /*
   * DATA NODES
   */  

  container attestation-results {
    presence 
      "An attestation Verifier has appraised the security posture of the
      device, and returned the results within this container.";
    description
      "Containes the latest Verifier appraisal of an Attester.";   
    leaf-list trustworthiness-vector {
      type identityref {
        base trustworthiness-level;
      }
      ordered-by system;
      description
        "One or more Trustworthiness Levels assigned which expose the 
        Verifiers evaluation of the Evidence associated with the 
        'tpmt-signature'.";
    }
    leaf timestamp {
      type yang:date-and-time;
      mandatory true;
      description
        "The timestamp of the Verifier's appraisal.";
    }
    leaf tpmt-signature {
      type binary;
      description
        "Must match a recent tpmt-signature sent in a notification to 
        a Verifier.  This allows correlation of the Attestation Results to
        a recent PCR change.";
    }
    leaf verifier-signature {
      type binary;
      mandatory true;
      description
        "Signature of the Verifier across all the current objects in the
        attestation-results container.";
    }
    leaf verifier-signature-key-name {
      type binary;
      description
        "Name of the key the Verifier used to sign the results.";
    }      
  }
}
